module augment-order-f {
  yang-version "1.1";
  namespace "urn:test:augment-order-f";
  prefix "ordf";

  import augment-order-target {
    prefix base;
  }

  augment "/base:root" {
    leaf leaf-f {
      type string;
      description "One of several sibling augments of the same target.";
    }
  }
}
