module augment-leaf-target {
  yang-version "1.1";
  namespace "urn:test:augment-leaf-target";
  prefix "al";

  container box {
    leaf target {
      type string;
    }
  }

  // Targeting a leaf is invalid (RFC 7950 §7.17); `nope` must not be
  // added under the leaf.
  augment "/al:box/al:target" {
    leaf nope {
      type string;
    }
  }
}
