module augment-order-a {
  yang-version "1.1";
  namespace "urn:test:augment-order-a";
  prefix "orda";

  import augment-order-target {
    prefix base;
  }

  augment "/base:root" {
    leaf leaf-a {
      type string;
      description "One of several sibling augments of the same target.";
    }
  }
}
