module augment-order-c {
  yang-version "1.1";
  namespace "urn:test:augment-order-c";
  prefix "ordc";

  import augment-order-target {
    prefix base;
  }

  augment "/base:root" {
    leaf leaf-c {
      type string;
      description "One of several sibling augments of the same target.";
    }
  }
}
